(defun test1 (disp / pt pt2 osmode)
    (setq oldosmode (getvar "osmode"))
    (setvar "osmode" (logior (getvar "osmode") 16384))
    (setq pt (list 1 1 1))
    (command "ucs" "")
    (command "ucs" '(10 0 0) "")
    (setq pt2 (trans pt 0 1 disp))
    (princ "\n变换后坐标是：")
    (princ pt2)
    
    (setvar "osmode" oldosmode)
    (princ)
)
(defun test2 (disp / pt pt2 osmode)
    (setq oldosmode (getvar "osmode"))
    (setvar "osmode" (logior (getvar "osmode") 16384))
    (setq pt (list 1 1 1))
    (command "ucs" "")
    (command "ucs" "x" "45")
    (setq pt2 (trans pt 0 1 disp))
    (princ "\n变换后坐标是：")
    (princ pt2)
    
    (setvar "osmode" oldosmode)
    (princ)
)

(defun test3 (disp / pt pt2 osmode)
    (setq oldosmode (getvar "osmode"))
    (setvar "osmode" (logior (getvar "osmode") 16384))
    (setq pt (list 1 1 1))
    (command "ucs" "")
    (command "ucs" '(10 0 0) "")
    (command "ucs" "x" "45")
    (setq pt2 (trans pt 0 1 disp))
    (princ "\n变换后坐标是：")
    (princ pt2)
    
    (setvar "osmode" oldosmode)
    (princ)
)
